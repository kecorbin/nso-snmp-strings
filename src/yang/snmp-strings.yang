module snmp-strings {

  namespace "http://example.com/snmp-strings";
  prefix snmp-strings;

  import ietf-inet-types {
    prefix inet;
  }
  import tailf-common {
    prefix tailf;
  }
  import tailf-ncs {
    prefix ncs;
  }

  description
    "Bla bla...";

  revision 2016-01-01 {
    description
      "Initial revision.";
  }

  list snmp-strings {
    description "This is an RFS skeleton service";

    key name;
    leaf name {
      tailf:info "Unique service id";
      tailf:cli-allow-range;
      type string;
    }

    uses ncs:service-data;
    ncs:servicepoint snmp-strings-servicepoint;

    list devices {
          key device_name;

          leaf device_name {
            type leafref {
              path "/ncs:devices/ncs:device/ncs:name";
            }
          }
    }

  
    leaf readonly {
      type string;
    }
    leaf readwrite {
      type string;
    }
  }
}
